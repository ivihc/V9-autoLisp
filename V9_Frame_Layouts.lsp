;;; V9_Frame_Layouts.lsp | AutoCAD for Windows | command: V9LAYOUT
;;; Model: WCS XY, lower-left insertion point, landscape ISO frame at uniform scale.
(vl-load-com)
(defun v9f:sizes () '(("A0" 1189 841) ("A1" 841 594) ("A2" 594 420)
  ("A3" 420 297) ("A4" 297 210) ("A5" 210 148)))
(defun v9f:frame (ent / obj key size p sx sy normal angle)
  (setq obj (vlax-ename->vla-object ent)
        key (strcase (vla-get-EffectiveName obj)))
  (if (and (wcmatch key "V9_DRAWING FRAME_A[0-5]")
           (setq size (assoc (substr key (1- (strlen key))) (v9f:sizes))))
    (progn
      (setq sx (vla-get-XScaleFactor obj) sy (vla-get-YScaleFactor obj)
            normal (vlax-get obj 'Normal) angle (vla-get-Rotation obj))
      (if (and (> sx 0) (equal sx sy (* sx 1e-8))
               (equal normal '(0.0 0.0 1.0) 1e-8) (> (cos angle) 0.999999999999))
        (progn (setq p (vlax-get obj 'InsertionPoint))
               (list size (car p) (cadr p) sx (vla-get-Handle obj) (caddr p)))
        (princ (strcat "\nBo qua " key " #" (vla-get-Handle obj)
                       ": khung xoay, lat hoac scale X/Y khong deu."))))))

(defun v9f:before (a b)
  (cond ((/= (nth 2 a) (nth 2 b)) (> (nth 2 a) (nth 2 b)))
        ((/= (nth 1 a) (nth 1 b)) (< (nth 1 a) (nth 1 b)))
        (T (< (nth 4 a) (nth 4 b)))))
(defun v9f:pick (/ ss i row rows)
  (princ "\nQuet chon cac khung trong Model. Giu Shift + nhap chuot trai de bo khung. Enter de tao layout.")
  (setq savedPick (getvar "PICKADD"))
  (if (= savedPick 0) (setvar "PICKADD" 2))
  (setq ss (ssget '((0 . "INSERT") (410 . "Model"))))
  (setvar "PICKADD" savedPick)
  (setq savedPick nil)
  (if ss
    (progn
      (setq i 0)
      (repeat (sslength ss)
        (setq row (v9f:frame (ssname ss i)) i (1+ i))
        (if (listp row) (if row (setq rows (cons row rows)))))
      (vl-sort rows 'v9f:before))))
(defun v9f:find-name (name names / result item)
  (foreach item names (if (= (strcase item) (strcase name)) (setq result item)))
  result)
(defun v9f:media (sheet names / key w h name dims target rev found alt)
  (setq key (car sheet) w (itoa (cadr sheet)) h (itoa (caddr sheet))
        target (strcat w "X" h) rev (strcat h "X" w))
  (foreach name names
    (if (wcmatch (strcase name) (strcat "ISO_FULL_BLEED_" key "_(*"))
      (progn
        (setq dims (substr name (+ 2 (vl-string-search "(" name))))
        (if (vl-string-search "_X_" (strcase dims))
          (progn
            (setq dims (strcat (itoa (fix (+ 0.5 (atof dims)))) "X"
                        (itoa (fix (+ 0.5 (atof (substr dims (+ 4 (vl-string-search "_X_" (strcase dims))))))))))
            (cond ((= dims target) (setq found (list name 0)))
                  ((= dims rev) (setq alt (list name 1)))))))))
  (if found found alt))
(defun v9f:tag (obj key value / a b)
  (regapp key)
  (setq a (vlax-make-safearray vlax-vbInteger '(0 . 1))
        b (vlax-make-safearray vlax-vbVariant '(0 . 1)))
  (vlax-safearray-fill a '(1001 1000))
  (vlax-safearray-fill b (list (vlax-make-variant key) (vlax-make-variant value)))
  (vla-SetXData obj a b))
(defun v9f:readtag (obj key / d)
  (setq d (assoc -3 (entget (vlax-vla-object->ename obj) (list key))))
  (if d (cdr (assoc 1000 (cdadr d)))))
(defun v9f:names (collection / obj result)
  (vlax-for obj collection (setq result (cons (vla-get-Name obj) result)))
  result)
(defun v9f:setup (sheet / key cfgs cfg base name n device media names pc origin)
  (setq key (car sheet) base (strcat "V9_PDF_" key) name base n 1
        cfgs (vla-get-PlotConfigurations doc) names (v9f:names cfgs))
  (while (and (v9f:find-name name names)
              (/= key (v9f:readtag (vla-Item cfgs name) "V9FRAMESETUP")))
    (setq n (1+ n) name (strcat base "_" (itoa n))))
  (if (v9f:find-name name names)
    (setq cfg (vla-Item cfgs name))
    (setq cfg (vla-Add cfgs name :vlax-false) pendingCfg cfg))
  (vla-RefreshPlotDeviceInfo cfg)
  (setq names (vlax-invoke cfg 'GetPlotDeviceNames))
  (foreach pc '("DWG To PDF.pc3" "AutoCAD PDF (General Documentation).pc3"
                "AutoCAD PDF (High Quality Print).pc3")
    (if (and (not media) (setq device (v9f:find-name pc names)))
      (progn
        (vla-put-ConfigName cfg device) (vla-RefreshPlotDeviceInfo cfg)
        (setq media (v9f:media sheet (vlax-invoke cfg 'GetCanonicalMediaNames))))))
  (cond
    ((not media) (setq why (strcat "Khong co PC3 PDF voi ISO full bleed " key)) nil)
    ((not (v9f:find-name "monochrome.ctb" (vlax-invoke cfg 'GetPlotStyleTableNames)))
      (setq why "Khong tim thay monochrome.ctb.") nil)
    (T
      (vla-put-PaperUnits cfg 1)
      (vla-put-CanonicalMediaName cfg (car media))
      (vla-put-PlotRotation cfg (cadr media))
      (vla-put-PlotType cfg 5)
      (setq origin (vlax-make-safearray vlax-vbDouble '(0 . 1)))
      (vlax-safearray-fill origin '(0.0 0.0))
      (vla-put-PlotOrigin cfg origin)
      (vla-put-UseStandardScale cfg :vlax-false)
      (vla-SetCustomScale cfg 1.0 1.0)
      (vla-put-StyleSheet cfg "monochrome.ctb")
      (vla-put-PlotWithPlotStyles cfg :vlax-true)
      (vla-put-PlotViewportBorders cfg :vlax-false)
      (v9f:tag cfg "V9FRAMESETUP" key)
      (setq pendingCfg nil) cfg)))
(defun v9f:vplayer (/ layers layer name n)
  (setq layers (vla-get-Layers doc) name "V9_FRAME_VIEWPORT" n 1)
  (while (and (tblsearch "LAYER" name)
              (progn (setq layer (vla-Item layers name))
                (or (= :vlax-true (vla-get-Plottable layer))
                    (= :vlax-true (vla-get-Lock layer))
                    (= :vlax-false (vla-get-LayerOn layer))
                    (= :vlax-true (vla-get-Freeze layer)))))
    (setq n (1+ n) name (strcat "V9_FRAME_VIEWPORT_" (itoa n))))
  (if (not (tblsearch "LAYER" name))
    (progn (setq layer (vla-Add layers name)) (vla-put-Plottable layer :vlax-false)))
  name)
(defun v9f:viewport (row / size w h x y z scale vp)
  (setq size (car row) w (cadr size) h (caddr size) x (nth 1 row) y (nth 2 row)
        z (nth 5 row) scale (nth 3 row))
  (setq vp (vla-AddPViewport (vla-get-PaperSpace doc) (vlax-3d-point (/ w 2.0) (/ h 2.0) 0.0) w h))
  (setq pendingVp vp)
  (vla-put-Layer vp vpLayer)
  (vla-put-Direction vp (vlax-3d-point 0 0 1))
  (vla-put-TwistAngle vp 0.0)
  (vla-Display vp :vlax-true)
  (vla-put-MSpace doc :vlax-true)
  (vla-put-ActivePViewport doc vp)
  (vla-ZoomWindow app (vlax-3d-point x y z) (vlax-3d-point (+ x (* w scale)) (+ y (* h scale)) z))
  (vla-put-StandardScale vp 1)
  (vla-put-CustomScale vp (/ 1.0 scale))
  (vla-put-MSpace doc :vlax-false)
  (vla-put-DisplayLocked vp :vlax-true)
  (v9f:tag vp "V9FRAMEVIEW" (nth 4 row))
  vp)
(defun v9f:make-layout (row cfg / size w h x y z scale n name lay blk obj old vp)
  (setq size (car row) w (cadr size) h (caddr size) x (nth 1 row) y (nth 2 row)
        z (nth 5 row) scale (nth 3 row) n 1)
  (while (member (strcase (setq name (strcat (car size) "_(" (itoa n) ")"))) occupied)
    (setq n (1+ n)))
  (setq lay (vla-Add layouts name) pendingLayout lay)
  (vla-put-ActiveLayout doc lay)
  (vla-put-MSpace doc :vlax-false)
  (vla-CopyFrom lay cfg)
  (vla-put-TabOrder lay (1- (vla-get-Count layouts)))
  (setq blk (vla-get-Block lay))
  (vlax-for obj blk
    (if (and (= (vla-get-ObjectName obj) "AcDbViewport")
             (/= 1 (cdr (assoc 69 (entget (vlax-vla-object->ename obj))))))
      (setq old (cons obj old))))
  (foreach obj old (vla-Delete obj))
  (v9f:viewport row)
  (v9f:tag lay "V9FRAMEHANDLE" (nth 4 row))
  (setq occupied (cons (strcase name) occupied) pendingLayout nil pendingVp nil)
  lay)

(defun v9f:clean ()
  (if pendingVp
    (progn
      (vl-catch-all-apply 'vla-put-MSpace (list doc :vlax-false))
      (vl-catch-all-apply 'vla-Delete (list pendingVp))
      (setq pendingVp nil)))
  (if pendingLayout
    (progn
      (if (= (getvar "TILEMODE") 0)
        (vl-catch-all-apply 'vla-put-MSpace (list doc :vlax-false)))
      (vl-catch-all-apply 'vla-put-ActiveLayout (list doc original))
      (vl-catch-all-apply 'vla-Delete (list pendingLayout))
      (setq pendingLayout nil)))
  (if pendingCfg (progn (vl-catch-all-apply 'vla-Delete (list pendingCfg)) (setq pendingCfg nil)))
)
(defun v9f:process (row / sheet key record cfg result lay old obj oldVp)
  (setq sheet (car row) key (car sheet) old (assoc (nth 4 row) linked)
        record (assoc key setups))
  (if (not record)
    (progn
      (setq why nil cfg (vl-catch-all-apply 'v9f:setup (list sheet)))
      (if (vl-catch-all-error-p cfg) (setq why (vl-catch-all-error-message cfg) cfg nil))
      (setq record (list key cfg why) setups (cons record setups))))
  (cond
    ((not (cadr record))
      (setq failed (1+ failed)) (princ (strcat "\n" key ": " (caddr record))))
    (T
      (if old
        (progn
          (setq lay (cdr old))
          (vla-put-ActiveLayout doc lay)
          (vla-CopyFrom lay (cadr record))
          (vlax-for obj (vla-get-Block lay)
            (if (and (= "AcDbViewport" (vla-get-ObjectName obj))
                     (= (nth 4 row) (v9f:readtag obj "V9FRAMEVIEW")))
              (setq oldVp obj)))
          (v9f:viewport row)
          (if oldVp (vla-Delete oldVp))
          (setq pendingVp nil)
          (v9f:tag lay "V9FRAMEHANDLE" (nth 4 row))
          (setq reused (1+ reused)))
        (progn
          (setq lay (v9f:make-layout row (cadr record)) made (1+ made))
          (princ (strcat "\nLayout: " (vla-get-Name lay)))))
      )))
(defun c:V9LAYOUT (/ *error* app doc original layouts occupied linked setups vpLayer savedPick rows
                     row obj handle result pendingLayout pendingVp pendingCfg why mark
                     made reused failed)
  (defun *error* (msg)
    (v9f:clean)
    (if original (vl-catch-all-apply 'vla-put-ActiveLayout (list doc original)))
    (if savedPick (setvar "PICKADD" savedPick))
    (if mark (vl-catch-all-apply 'vla-EndUndoMark (list doc)))
    (if msg (princ (strcat "\nV9LAYOUT: " msg))) (princ))
  (setq app (vlax-get-acad-object) doc (vla-get-ActiveDocument app)
        original (vla-get-ActiveLayout doc) layouts (vla-get-Layouts doc)
        made 0 reused 0 failed 0)
  (cond
    ((/= (getvar "TILEMODE") 1) (princ "\nChuyen sang tab Model roi chay V9LAYOUT."))
    ((= (getvar "PSTYLEMODE") 0) (princ "\nDWG dang dung STB. Can ban ve CTB de gan monochrome.ctb."))
    ((not (setq rows (v9f:pick))) (princ "\nKhong co khung A0-A5 hop le trong vung chon."))
    (T
      (vla-StartUndoMark doc) (setq mark T)
      (setq vpLayer (v9f:vplayer))
      (vlax-for obj layouts
        (setq occupied (cons (strcase (vla-get-Name obj)) occupied))
        (if (setq handle (v9f:readtag obj "V9FRAMEHANDLE"))
          (setq linked (cons (cons handle obj) linked))))
      (foreach row rows
        (setq result (vl-catch-all-apply 'v9f:process (list row)))
        (if (vl-catch-all-error-p result)
          (progn (setq failed (1+ failed))
            (princ (strcat "\nKhung #" (nth 4 row) ": " (vl-catch-all-error-message result)))))
        (v9f:clean))
      (vla-put-ActiveLayout doc original)
      (vla-EndUndoMark doc) (setq mark nil)
      (princ (strcat "\nLayout moi: " (itoa made) " | Da co: " (itoa reused)
              " | Loi layout: " (itoa failed)))))
  (princ))
(princ "\nV9 Frame Layouts R3 da nap. Chuyen sang Model va go V9LAYOUT.")
(princ)
